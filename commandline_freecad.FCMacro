import FreeCAD, FreeCADGui
from PySide2.QtWidgets import (
    QLineEdit, QVBoxLayout, QWidget, QDockWidget, QListWidget, QListWidgetItem, QTextEdit
)
from PySide2.QtCore import Qt, QEvent
import unicodedata
import difflib
import re
from FreeCAD import Units

commands_used = []

class CommandBar(QWidget):
    def __init__(self, parent=None):
        super().__init__(parent)

        self.layout = QVBoxLayout()
        self.command_input = QLineEdit(self)
        self.command_input.setPlaceholderText("Type a command or (Object).Property = value")
        self.command_list = QListWidget(self)
        self.command_list.setVisible(False)
        self.command_list.itemActivated.connect(self.select_command)
        self.console_output = QTextEdit(self)
        self.console_output.setReadOnly(True)
        self.console_output.setStyleSheet("background-color: #313651; color: white; font-family: Consolas;")
        self.layout.addWidget(self.command_input)
        self.layout.addWidget(self.command_list)
        self.layout.addWidget(self.console_output)
        self.setLayout(self.layout)

        self.commands = self.get_commands_context()
        self.command_names = [item["name"] for item in self.commands]
        self.active_object_label = None

        self.command_input.textChanged.connect(self.update_suggestions)
        self.command_input.installEventFilter(self)

        FreeCADGui.getMainWindow().installEventFilter(self)

    def get_commands_context(self):
        all_commands = []
        commands = FreeCADGui.listCommands()
        for cmd_name in commands:
            cmd = FreeCADGui.Command.get(cmd_name)
            if cmd:
                actions = cmd.getAction()
                if actions:
                    action = actions[0] if isinstance(actions, list) else actions
                    if action:
                        menu_text = action.text()
                        all_commands.append({"name": f"{menu_text.translate({ord('&'): None})} (cmd)", "command": cmd_name})
        if FreeCAD.ActiveDocument:
            for obj in FreeCAD.ActiveDocument.Objects:
                all_commands.append({"name": f"({obj.Label})", "command": f"__select__:{obj.Name}"})
        return all_commands

    def normalize(self, text):
        text = text.lower()
        return ''.join(c for c in unicodedata.normalize('NFKD', text) if not unicodedata.combining(c)).strip()

    def update_suggestions(self):
        user_input = self.command_input.text().strip()
        self.command_list.clear()
        self.commands = self.get_commands_context()
        self.command_names = [item["name"] for item in self.commands]

        prop_match = re.match(r"\((.+?)\)\.([a-zA-Z0-9_.]*)$", user_input)
        if prop_match:
            obj_label = prop_match.group(1).strip()
            partial_prop = prop_match.group(2).strip()
            obj = next((o for o in FreeCAD.ActiveDocument.Objects if self.normalize(o.Label) == self.normalize(obj_label)), None)
            if obj:
                props = list(obj.PropertiesList)
                if hasattr(obj, "Placement"):
                    props += ["Placement.Base", "Placement.Rotation", "Placement.Base.x", "Placement.Base.y", "Placement.Base.z"]
                filtered = [p for p in props if self.normalize(p).startswith(self.normalize(partial_prop))]
                for p in sorted(filtered):
                    self.command_list.addItem(QListWidgetItem(p))
                self.command_list.setVisible(bool(filtered))
                self.active_object_label = obj_label
                return

        self.active_object_label = None
        norm_input = self.normalize(user_input)
        if norm_input:
            matches = sorted(
                self.command_names,
                key=lambda name: difflib.SequenceMatcher(None, norm_input, self.normalize(name)).ratio(),
                reverse=True
            )
            for match in matches[:10]:
                self.command_list.addItem(QListWidgetItem(match))
            self.command_list.setVisible(bool(matches))
        else:
            for command_used in commands_used:
                self.command_list.addItem(QListWidgetItem(command_used))
            self.command_list.setVisible(True)

    def eventFilter(self, obj, event):
        if event.type() == QEvent.KeyPress:
            key = event.key()
            if key == Qt.Key_Escape:
                if not self.command_input.hasFocus():
                    self.command_input.setFocus()
                else:
                    self.command_input.clear()
                    self.command_list.setVisible(False)
                    self.command_input.clearFocus()
                return True
            elif key in (Qt.Key_Return, Qt.Key_Enter):
                if self.command_list.isVisible() and self.command_list.currentItem():
                    self.select_command(self.command_list.currentItem())
                else:
                    self.execute_command()
                    self.command_list.setVisible(False)
                return True
            elif key == Qt.Key_Tab and self.command_list.isVisible() and self.command_list.currentItem():
                item_text = self.command_list.currentItem().text()
                if self.active_object_label:
                    self.command_input.setText(f"({self.active_object_label}).{item_text}")
                else:
                    self.command_input.setText(item_text)
                self.command_input.setFocus()
                self.command_input.cursorForward(False, len(self.command_input.text()))
                return True
            elif key in (Qt.Key_Backspace, Qt.Key_Delete, Qt.Key_Control):
                return False
            if self.command_list.isVisible():
                if key == Qt.Key_Down:
                    next_index = (self.command_list.currentRow() + 1) % self.command_list.count()
                    self.command_list.setCurrentRow(next_index)
                    return True
                elif key == Qt.Key_Up:
                    prev_index = (self.command_list.currentRow() - 1) % self.command_list.count()
                    self.command_list.setCurrentRow(prev_index)
                    return True
            else:
                self.command_list.setVisible(True)
            if event.text().strip():
                self.command_input.setFocus()
                self.command_input.insert(event.text())
                return True
        return super().eventFilter(obj, event)

    def select_command(self, item):
        if item:
            if self.active_object_label:
                self.command_input.setText(f"({self.active_object_label}).{item.text()}")
            else:
                self.command_input.setText(item.text())

    def execute_command(self):
        input_command = self.command_input.text().strip()

        if "=" in input_command:
            try:
                left, right = input_command.split("=", 1)
                left = left.strip()
                right = right.strip()

                match = re.match(r"\((.+?)\)\.(.+)", left)
                if match:
                    obj_label = match.group(1).strip()
                    attr_chain = match.group(2).strip()
                else:
                    self.console_output.setPlainText(f"Error: usa la sintaxis (Objeto).Propiedad = Valor\n" + self.console_output.toPlainText())
                    return

                obj = next((o for o in FreeCAD.ActiveDocument.Objects if self.normalize(o.Label) == self.normalize(obj_label)), None)
                if not obj:
                    self.console_output.setPlainText(f"Objeto no encontrado: {obj_label}\n" + self.console_output.toPlainText())
                    return

                try:
                    if (right.startswith('"') and right.endswith('"')) or (right.startswith("'") and right.endswith("'")):
                        value = right[1:-1]
                    else:
                        q = Units.Quantity(right)
                        value = q.Value
                        if q.getUnit().isEmpty() and value == int(value):
                            value = int(value)
                except Exception:
                    try:
                        value = eval(right, {"__builtins__": {}}, {})
                    except:
                        value = right

                context = {"obj": obj}
                exec(f"obj.{attr_chain} = {repr(value)}", context)

                obj.Document.recompute()
                FreeCADGui.updateGui()

                self.console_output.setPlainText(f"Set ({obj.Label}).{attr_chain} = {value}\n" + self.console_output.toPlainText())

                if input_command in commands_used:
                    commands_used.remove(input_command)
                commands_used.reverse()
                commands_used.append(input_command)
                commands_used.reverse()
                del commands_used[4:]

                self.command_input.clear()
                self.command_list.setVisible(False)
                self.command_input.clearFocus()
                self.active_object_label = None
            except Exception as e:
                self.console_output.setPlainText(f"Error interpretando asignación: {e}\n" + self.console_output.toPlainText())
            return

        selected_command = next((item["command"] for item in self.commands if item["name"] == input_command), None)
        if selected_command:
            try:
                if selected_command.startswith("__select__:"):
                    obj_name = selected_command.split(":")[1]
                    obj = FreeCAD.ActiveDocument.getObject(obj_name)
                    if obj:
                        FreeCADGui.Selection.clearSelection()
                        FreeCADGui.Selection.addSelection(obj)
                        self.console_output.setPlainText(f"Selected: {obj.Label}\n" + self.console_output.toPlainText())
                else:
                    FreeCADGui.runCommand(selected_command)
                    self.console_output.setPlainText(f"Executing command: {selected_command}\n" + self.console_output.toPlainText())

                    if input_command in commands_used:
                        commands_used.remove(input_command)
                    commands_used.reverse()
                    commands_used.append(input_command)
                    commands_used.reverse()
                    del commands_used[4:]

                self.command_input.clear()
                self.command_list.setVisible(False)
                self.command_input.clearFocus()
                self.active_object_label = None
            except Exception as e:
                self.console_output.setPlainText(f"Error on exec. {selected_command}: {e}\n" + self.console_output.toPlainText())
        else:
            self.console_output.setPlainText(f"Command not found or invalid: {input_command}\n" + self.console_output.toPlainText())

def show_command_bar():
    main_window = FreeCADGui.getMainWindow()
    dock = QDockWidget("Commandline bar", main_window)
    dock.setAllowedAreas(Qt.TopDockWidgetArea | Qt.BottomDockWidgetArea | Qt.RightDockWidgetArea)
    command_bar = CommandBar()
    dock.setWidget(command_bar)
    main_window.addDockWidget(Qt.RightDockWidgetArea, dock)

show_command_bar()
